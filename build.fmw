FME workspace build.fmw

Parameters:
- FME_ACADEMY_BASEDIR = D:\fme_general\training\FMETraining   # FME Academy Source Folder
- OUTPUT_FOLDER = $(FME_MF_DIR)build   # Output Folder
- EXTRACT_ARCHIVES = Yes   # Extract Archives

Writers:
- HTML_1: HTML to $(OUTPUT_FOLDER)\modules

FilenamePartExtractor
    DIRNAME_ATTR = _dirname
    DIRPATH_ATTR = _dirpath
    ROOTNAME_ATTR = fme_feature_type
    SRC_ATTR = @Value(zip_path)
    -> AttributeFilter
AttributeFilter
    ATTR_NAME = fme_feature_type
    ATTR_VALUES = <Empty>,<Missing>,<Null>,<Unfiltered>,module,labels,evaluation,trail
    <EMPTY> -> AttributeFilter__Empty_
    <MISSING> -> AttributeFilter__Missing_
    <NULL> -> AttributeFilter__Null_
    <UNFILTERED> -> AttributeFilter__Unfiltered_
    module -> AttributeRenamer_2
    labels -> FilenamePartExtractor_3
    evaluation -> AttributeRenamer
    trail -> AttributeFilter_trail
AttributeFilter__Empty_: Inspector
AttributeFilter__Missing_: Inspector
AttributeFilter__Null_: Inspector
AttributeFilter__Unfiltered_: Inspector
AttributeFilter_trail: Logger
    LOG_FEATURE = LOG_ONLY
    MAXCOORDS = 20
    MAXFEATS = 20
    MESSAGE = Feature is:
    SEVERITY = INFO
AttributeRenamer_2
    ATTR_TABLE = RENAME_SET_DEFAULT _dirname > module
    -> XMLTemplater [ROOT]
    -> XMLTemplater_2 [MODULE]
FilenamePartExtractor_3
    DIRNAME_ATTR = module
    SRC_ATTR = @Value(_dirpath)
    -> XMLTemplater_2 [LABELS]
AttributeRenamer
    ATTR_TABLE = RENAME_SET_DEFAULT _dirname > unit
    -> FilenamePartExtractor_2
FilenamePartExtractor_2
    DIRNAME_ATTR = module
    SRC_ATTR = @Value(_dirpath)
    -> XMLTemplater [UNIT_EVALUATION]

Bookmark: Read/Extract ZipFile(s)
Note: Read all **/*.json- and **/*.yaml-files / yaml is converted to json for futher processing / Optionally extract zipfile(s) into output folder
PythonPyYAML
PythonCreator
    NEW_ATTRIBUTES = fme_dataset zip_path json_data
    PYTHONSOURCE_NEW:
      import fmeobjects
      import os
      import os.path
      import zipfile
      import yaml
      import json

      '''
      Helper function because the yaml-files have keys with leading colon
      '''
      def strip_leading_suffix(d):
          if not isinstance(d, dict): return d
          return {
              [k, k[1:]][k.startswith(':')]: strip_leading_suffix(v)
              for k,v in d.items()
          }

      # Template Class
      class FeatureCreator(object):
          def __init__(self):
              self.src_folder = os.path.normpath(FME_MacroValues['FME_ACADEMY_BASEDIR'])
              self.dst_folder = os.path.normpath(FME_MacroValues['OUTPUT_FOLDER'])
              self.extract_archives = 'yes' == FME_MacroValues.get('EXTRACT_ARCHIVES', 'no').lower()
          def input(self,feature):
              for zip_filename in (s for s in os.listdir(self.src_folder) if s.endswith('.zip')):
                  zip_fp = os.path.join(self.src_folder, zip_filename)
                  zip_file_feature = feature.clone()
                  zip_file_feature.setAttribute('fme_dataset', zip_fp)
                  with zipfile.ZipFile(zip_fp) as zin:
                      if self.extract_archives:
                          if not os.path.exists(self.dst_folder):
                              os.makedirs(self.dst_folder)
                          zin.extractall(path=self.dst_folder)
                      for zinfo in (zinfo for zinfo in zin.infolist() if zinfo.filename.endswith('.json')):
                          json_feature = zip_file_feature.clone()
                          json_feature.setAttribute('zip_path', zinfo.filename)
                          json_feature.setAttribute('json_data', str(zin.read(zinfo), 'utf8'))
                          self.pyoutput(json_feature)
                      for zinfo in (zinfo for zinfo in zin.infolist() if zinfo.filename.endswith('.yml')):
                          yml_feature = zip_file_feature.clone()
                          yml_feature.setAttribute('zip_path', zinfo.filename)
                          yaml_data = str(zin.read(zinfo), 'utf8')
                          yaml_object = strip_leading_suffix(yaml.load(yaml_data, Loader=yaml.BaseLoader))
                          #yml_feature.setAttribute('yml_data', yaml_data)
                          yml_feature.setAttribute('json_data', json.dumps(yaml_object))
                          self.pyoutput(yml_feature)
                  #self.pyoutput(zip_file_feature)
          def close(self):
              pass
    PYTHONSYMBOL = FeatureCreator
    -> FilenamePartExtractor

Bookmark: JSON to HTML using XQuery
XMLTemplater
    CONSECUTIVE_GROUPS = No
    GROUP_BY = module
    OUTPUT_XML_HEADER = No
    RESULT_ATTRIBUTE = html_content
    ROOT_QUERY_EXPR:
      (: Note - the json-to-xml function will wrap array elements with an "el"-tag  :)
      declare function local:json-to-xml($item as item(), $name as xs:string) as element()* {
          if ($item instance of object()) then (
              element {$name}{
                  for $key in jn:keys($item)
                  return local:json-to-xml($item($key), $key)
              }
          )
          else if ($item instance of array()) then (
              element {$name}{
                  for $i in 1 to jn:size($item)
                  return local:json-to-xml($item($i), 'el')
              }
          )
          else (
              element {$name}{$item}
          )
      };

      let $module := local:json-to-xml(fme:get-json-attribute("json_data"), 'module')
      let $unit_evaluations := fme:process-features("UNIT_EVALUATION")

      return

      <div>
      {
      for $unit in $module/units/el
      let $unit_id := $unit/id/text()
      return <div>
          {
              for $e in $unit_evaluations
              where name($e) = $unit_id
              return (<h2>{$e/title/text()}</h2>,
               <div>
               {$e/total_mins/text()} minutes <br/>
               <a href="{$unit_id}/content.html">go</a>
               </div>)
          }

      </div>
      }
      </div>
    UNIT_EVALUATION_QUERY_EXPR:
      declare function local:json-to-xml($item as item(), $name as xs:string) as element()* {
          if ($item instance of object()) then (
              element {$name}{
                  for $key in jn:keys($item)
                  return local:json-to-xml($item($key), $key)
              }
          )
          else if ($item instance of array()) then (
              element {$name}{
                  for $i in 1 to jn:size($item)
                  return local:json-to-xml($item($i), 'el')
              }
          )
          else (
              element {$name}{$item}
          )
      };
      local:json-to-xml(fme:get-json-attribute("json_data"), fme:get-attribute("unit"))
    VISIBLE_QUERY_VALIDATE = Yes
    -> AttributeCreator_3
AttributeCreator_3
    ATTR_TABLE = SET_TO _fanout_dataset = @Value(module)\
    -> AttributeCreator
Note: This works... but is rather complex / Would probably be easier to flatten/fragmentize json and join together all bits and pieces using other methods
Creator
    GEOMTYPE = Geometry Object
    NUM = 1
    CREATED -> XMLTemplater_2 [ROOT]
XMLTemplater_2
    LABELS_QUERY_EXPR = fme:get-json-attribute("json_data")
    MODULE_QUERY_EXPR = fme:get-json-attribute("json_data")
    OUTPUT_XML_HEADER = No
    RESULT_ATTRIBUTE = html_content
    ROOT_QUERY_EXPR:
      declare function local:json-to-xml($item as item(), $name as xs:string) as element()* {
          if ($item instance of object()) then (
              element {$name}{
                  for $key in jn:keys($item)
                  return local:json-to-xml($item($key), $key)
              }
          )
          else if ($item instance of array()) then (
              element {$name}{
                  for $i in 1 to jn:size($item)
                  return local:json-to-xml($item($i), 'el')
              }
          )
          else (
              element {$name}{$item}
          )
      };

      let $modules := {
          for $e in fme:process-features("MODULE")
          return local:json-to-xml($e, 'module')
      }

      let $labels := {
          for $e in fme:process-features("LABELS")
          return local:json-to-xml($e, 'label')
      }


      return <html>
      <head>
      <meta charset="UTF-8" />
      <title>FME Academy</title>
      <link rel="stylesheet" href="mystyle.css"></link>
      </head>
      <body>
      <h1>FME Academy</h1>
      {
      for $module in $modules
      let $module_id := $module/id/text()
      return <div>
          {
              for $l in $labels//modules/*
              where name($l) = $module_id
              return (<h2>{$l/title/text()} <a href="./{$module_id}/index.html"><img width="50" height="50" src="./{$module_id}/badge.png" /></a></h2>,
               <div>{$l/description/text()}</div>)
          }

      </div>
      }
      </body>
      </html>
    VISIBLE_QUERY_VALIDATE = Yes
    -> AttributeCreator_2
AttributeCreator_2
    ATTR_TABLE = SET_TO _fanout_dataset
    -> AttributeCreator
AttributeCreator
    ATTR_TABLE:
      SET_TO html_content = <!DOCTYPE html>
        @CurrentAttribute()
    -> HTML (writer HTML_1)
HTML (writer HTML_1)
    attributes: html_content buffer
